# ChrgCtrl_req

## REQ_ChrgCtrl_IN01: [P_VehSpd] 输入 In_VehSpd（VehSpd，km/h，范围0~300） (Functional)

## REQ_ChrgCtrl_IN02: [P_DrvMode] 输入 In_DrvMode（En_DrvMode，none，范围0~2） (Functional)

## REQ_ChrgCtrl_OUT01: [P_DrvTrqReq] 输出 Out_DrvTrqReq（DrvTrqReq，Nm，范围-500~2000） (Functional)

## REQ_ChrgCtrl_CAL01: 标定 Cal_TrqMax（single，Nm，范围0~2000，初值1500） (Functional)

## REQ_ChrgCtrl_CAL02: 标定 Cal_TrqRate（single，Nm/s，范围0~5000，初值2000） (Functional)

## REQ_ChrgCtrl_RUN01: 周期任务 R_ChrgCtrl_10ms（10ms，访问P_VehSpd;P_DrvMode;P_DrvTrqReq） (Functional)
